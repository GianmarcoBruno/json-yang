module wood-types {
  prefix "wt";

  namespace "http://example.net/wood-types";
  revision 2018-06-01 {
    description
     "Wood types.";
  }

  /* Identities */
  identity wood-type {
    description "Base wood";
  }

  identity pine {
    base wood-type;
    description "Pine";
  }

  identity oak {
    base wood-type;
    description "Oak";
  }

  identity timber {
    base wood-type;
    description "Timber";
  }
}
