module dishwasher {
  yang-version 1.1;

  namespace "http://example.net/dishwasher";

  prefix "dw";

  import dishwasher-types {
    prefix "dwt";
  }

  contact
      "Gianmarco Bruno
       <mailto: gianmarco.bruno@gmail.com>
       Carlo Perocchio
       <mailto: carlo.perocchio@gmail.com>";

  description
    "Model for the dishwasher.";

  revision 2017-05-18 {
    description
      "Initial revision.";
  }

  feature remotely-managed {
    description
      "this feature means that some operations
       can be invoked remotely on the dishwasher";
  }

  /* Groupings */

  /* State data and Configuration */

  container dishwasher {
    description
      "State data and configuration of a dishwasher.";
    leaf phase {
      type identityref {
        base dwt:dishwasher-phase;
      }
      config "false";
      mandatory "true";
      description "Current state of the dishwasher.";
    }

    leaf cycle {
      type identityref {
        base dwt:dishwasher-cycle;
      }
      mandatory "true";
      description "Selected washing cycle.";
    }

    leaf operating {
      type boolean;
      mandatory "true";
      config "false";
      description "Operating status of the machine (true means all OK).";
    }

    leaf is-standalone {
      type empty;
    }

    leaf s-n {
      config false;
      mandatory true;
      type dwt:serial-number;
      // must argument is an XPath, so . refers to s-n
      must ". != 'XX476WW-E'" {
        description "disallowed S/N. S/N ends with -S or -E";
      }
      must ". != 'AS640MX-S'" {
        description "disallowed S/N. S/N ends with -S or -E";
      }
      /* seems not implemented by pyang
      must "re-match(., '..666..-..')" {
        description "disallowed S/N. S/N ends with -S or -E";
      }
      */

    }

      container admin {
         leaf owner {
            type string;
         }
      }
  }

  /* RPCs */

  rpc start-resume {
    description
      "Start the dishwasher - same method to resume.";
  }

  rpc cancel-drain {
    description
      "Cancel the cycle and drain.
      On purpose we assume that the input is the owner name";
      input {
        leaf user {
          type leafref {
            path "/dishwasher/admin/owner";
          }
        }
      }
  }

  rpc delay-by-hours {
    input {
      leaf delay-hour {
        type int8;
	/* restrict to 1..24 hours*/
      }
    }
    description
      "Start the dishwasher after given number of hours.";
  }

  rpc time-to-start {
    output {
      leaf delay-hour {
        type string {
          pattern
	  '((([0-1][0-9])|2[0-3]):[0-5][0-9])';
          length "5";
	}
      }
    }
    description
      "Time after which the dishwasher will start - displayed as HH:MM.";
  }

  /* Notifications */

  notification halted {
    description
      "The dishwasher has been halted for some problem";
    leaf state {
      type identityref {
        base dwt:dishwasher-phase;
      }
      mandatory "true";
      description
        "The state of the dishwasher when the problem occurred.";
    }
  }
}
