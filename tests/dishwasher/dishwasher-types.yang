module dishwasher-types {
  prefix "dwt";

  namespace "http://example.net/dishwasher-types";
  revision 2017-05-19 {
    description
     "Initial revision.";
  }

  /* Identities */

  /* Cycles */
  identity dishwasher-cycle {
    description
     "base identity for supported dishwasher cycles";
  }

  identity smart-wash {
    base dishwasher-cycle;
  }

  identity normal-start {
    base dishwasher-cycle;
  }

  identity light-start {
    base dishwasher-cycle;
  }

  identity fast-start {
    base dishwasher-cycle;
  }

  identity quick-rinse {
    base dishwasher-cycle;
  }

  /* Phases */
  identity dishwasher-phase {
  }

  identity stand-by {
    base dishwasher-phase;
  }

  identity warm-up {
    base dishwasher-phase;
  }

  identity washing {
    base dishwasher-phase;
  }

  identity drying {
    base dishwasher-phase;
  }

  typedef serial-number {
    type string {
      pattern '[A-Z][A-Z][0-9][0-9][0-9][A-Z][A-Z]-[E|S]';
    }
    description
      "Same code of EU car plates, just a regex";
    }
}
